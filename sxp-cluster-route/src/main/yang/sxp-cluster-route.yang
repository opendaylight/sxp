module sxp-cluster-route {
    yang-version 1;

    namespace "urn:opendaylight:sxp:cluster:route";
    prefix "sxpcroute";

    import ietf-inet-types { prefix inet; revision-date "2013-07-15"; }
    import ietf-yang-types { prefix ietf-yang; revision-date "2013-07-15"; }
    import sxp-database { prefix sxpdb; revision-date "2016-03-08"; }
    import sxp-node { prefix sxpnd; revision-date "2016-03-08"; }
    import sxp-filter { prefix sxpfl; revision-date "2015-09-11"; }
    import sxp-protocol { prefix sxppt; revision-date "2014-10-02"; }

    organization "Cisco Systems, Inc.";

    contact "Martin Mihalek <mamihale@cisco.com>";

    description
        "Module defines the sxp cluster routing configuration.";

    revision "2016-12-12" {
        description
                "Initial revision of SXP cluster route model";
    }


    container sxp-cluster-route {
        description "Sxp cluster routing configurations";

        list routing-definition {
            description "Multiple routing definitions";

            key ip-address;
            leaf ip-address {
                type inet:ip-address;
                mandatory true;
            }
            leaf interface {
                description "Local network interface (hosting virtual interface)";
                type string {
                    length "1..64";
                }
                mandatory true;
            }
            leaf netmask {
                description "Network mask to be used with virtual interface";
                type inet:ip-address;
                mandatory true;
            }
            leaf timestamp {
                description "Timestamp marks last succesfull editation of route";
                type ietf-yang:date-and-time;
                config false;
            }
            leaf consistent {
                description "If this routing is consistent with system";
                config false;
                type boolean;
                default true;
            }
            leaf info {
                description "Explanation / cause of current state";
                config false;
                type string;
            }
        }
    }
}
