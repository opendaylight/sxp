module sxp-controller {
    yang-version 1;

    namespace "urn:opendaylight:sxp:controller";
    prefix "sxpctrl";

    import ietf-inet-types { prefix inet; revision-date "2013-07-15"; }
    import sxp-database { prefix sxpdb; revision-date "2016-03-08"; }
    import sxp-node { prefix sxpnd; revision-date "2016-03-08"; }
    import sxp-filter { prefix sxpfl; revision-date "2015-09-11"; }
    import sxp-protocol { prefix sxppt; revision-date "2014-10-02"; }
    import sxp-config { prefix sxpcfg; revision-date "2018-06-11"; }

    organization "Cisco Systems, Inc.";

    contact "Martin Mihalek <mamihale@cisco.com>";

    description
        "Module defines the base YANG definitions for ODL-SXP-aware network
        node.";

    revision "2014-10-02" {
        description
                "Reviewed revision of SXP controller model";
    }

    typedef config-persistence {
        type enumeration {
            enum pernament;
            enum operational;
        }
        description "If the Configuration will be preserved after shutdown";
    }

    // ***************************************
    // Master Database Configuration Groupings
    // ***************************************

    grouping master-database-configuration-fields {
        description "Standard configuration for master database";
        list binding {
            key "sgt";
            leaf sgt {
                type sxpdb:sgt;
                description "Assigned source group tag";
            }
            leaf-list ip-prefix {
                type inet:ip-prefix;
                min-elements 1;
                description "Assigned IPv4/IPv6 host IP or network address (prefix is less than 32/64).";
            }
        }
    }

    grouping master-database-configuration {
        description "Standard configuration for SXP database";
        container master-database {
            uses master-database-configuration-fields;
        }
        leaf origin {
            mandatory true;
            type leafref {
                path "/sxpcfg:binding-origins/sxpcfg:binding-origin/sxpcfg:origin";
            }
        }
    }

    // **************
    // RPC Definition
    // **************

    rpc get-connections {
        input {
            leaf requested-node {
                type sxppt:node-id;
                mandatory true;
                description "Optional: SXP node ID";
            }
            leaf domain-name {
                type string;
                default "global";
            }
        }
        description "Get all connections status of a specified node";
        output {
            uses sxpnd:sxp-connections-fields;
        }
    }

    rpc add-connection {
        input {
            leaf config-persistence {
                type config-persistence;
                default "pernament";
            }
            leaf requested-node {
                type sxppt:node-id;
                mandatory true;
                description "Optional: SXP node ID";
            }
            leaf domain-name {
                type string;
                default "global";
            }
            uses sxpnd:sxp-connections-fields;
        }
        description "Create a new connection for a specified node";
        output {
            leaf result {
                type boolean;
            }
        }
    }

    rpc delete-connection {
        description "Delete a connection of a specified node";
        input {
            leaf requested-node {
                type sxppt:node-id;
                mandatory true;
                description "Optional: SXP node ID";
            }
            leaf domain-name {
                type string;
                default "global";
            }
            leaf peer-address {
                type inet:ipv4-address;
                mandatory true;
                description "Address of the connected peer";
            }
            leaf tcp-port {
                type inet:port-number;
                default "64999";
                description "Port of the connected peer";
            }
        }
        output {
            leaf result {
                type boolean;
            }
        }
    }

    rpc get-node-bindings {
        description "RPC returns IP-SGT bindings configuration of a specified
                node";
        input {
            leaf requested-node {
                type sxppt:node-id;
                mandatory true;
                description "Node ID of the dedicated SXP source";
            }
            leaf domain-name {
                type string;
                default "global";
            }
            leaf bindings-range {
                type enumeration {
                    enum local;
                    enum all;
                }
                default local;
            }
        }
        output {
            uses master-database-configuration-fields;
        }
    }

    rpc add-peer-group {
        description "Add new PeerGroup in specified Node";
        input {
            leaf config-persistence {
                type config-persistence;
                default "pernament";
            }
            leaf requested-node {
                type sxppt:node-id;
                mandatory true;
                description "Node ID of the dedicated SXP source";
            }
            uses sxpfl:sxp-peer-group;
        }
        output {
            leaf result {
                type boolean;
            }
        }
    }

    rpc delete-peer-group {
        description "Removes PeerGroup in specified node";
        input {
            leaf requested-node {
                type sxppt:node-id;
                mandatory true;
                description "Node ID of the dedicated SXP source";
            }
            leaf peer-group-name {
                type string;
                mandatory true;
                description "Name of PeerGroup that will be removed";
            }
        }
        output {
            leaf result {
                type boolean;
            }
        }
    }

    rpc get-peer-group {
        description "Gets PerGroup with specified name on node";
        input {
            leaf requested-node {
                type sxppt:node-id;
                mandatory true;
                description "Node ID of the dedicated SXP source";
            }
            leaf peer-group-name {
                type string;
                mandatory true;
                description "Name of peer group";
            }
        }
        output {
            uses sxpfl:sxp-peer-group;
        }
    }

    rpc get-peer-groups {
        description "Gets all PeerGroups on specified node";
        input {
            leaf requested-node {
                type sxppt:node-id;
                mandatory true;
                description "Node ID of the dedicated SXP source";
            }
        }
        output {
            uses sxpfl:sxp-peer-groups;
        }
    }

    rpc add-filter {
        description "Add new filter to PeerGroup";
        input {
            leaf config-persistence {
                type config-persistence;
                default "pernament";
            }
            leaf requested-node {
                type sxppt:node-id;
                mandatory true;
                description "Node ID of the dedicated SXP source";
            }
            leaf peer-group-name {
                type string;
                mandatory true;
                description "Name of PeerGroup where filter will be placed";
            }
            uses sxpfl:sxp-filter;
        }
        output {
            leaf result {
                type boolean;
            }
        }
    }

    rpc delete-filter {
        description "Removes filter from PeerGroup";
        input {
            leaf requested-node {
                type sxppt:node-id;
                mandatory true;
                description "Node ID of the dedicated SXP source";
            }
            leaf peer-group-name {
                type string;
                mandatory true;
                description "Name of PeerGroup from where filter will be removed";
            }
            leaf filter-type {
                type sxpfl:filter-type;
                mandatory true;
            }
            leaf filter-specific {
                type sxpfl:filter-specific;
            }
        }
        output {
            leaf result {
                type boolean;
            }
        }
    }

    rpc update-filter {
        description "Updates Filter in specified PeerGroup";
        input {
            leaf config-persistence {
                type config-persistence;
                default "pernament";
            }
            leaf requested-node {
                type sxppt:node-id;
                mandatory true;
                description "Node ID of the dedicated SXP source";
            }
            leaf peer-group-name {
                type string;
                mandatory true;
                description "Name of PeerGroup where filter will be updated";
            }
            uses sxpfl:sxp-filter;
        }
        output {
            leaf result {
                type boolean;
            }
        }
    }

    rpc add-node {
        description "Create a new connection for a specified node";
        input {
            leaf config-persistence {
                type config-persistence;
                default "pernament";
            }
            leaf node-id {
                type sxppt:node-id;
                mandatory true;
                description "SXP node ID";
            }
            uses sxpnd:sxp-node-identity-fields;
            uses sxpnd:sxp-node-buffering-fields;
        }
        output {
            leaf result {
                type boolean;
            }
        }
    }

    rpc delete-node {
        description "Delete a node from ODL";
        input {
            leaf node-id {
                type sxppt:node-id;
                mandatory true;
                description "SXP node ID";
            }
        }
        output {
            leaf result {
                type boolean;
            }
        }
    }

    rpc add-domain {
        description "Add Domain into node";
        input {
            leaf node-id {
                type sxppt:node-id;
                mandatory true;
                description "SXP node ID";
            }
            leaf domain-name {
                type string;
                mandatory true;
            }
            uses sxpnd:sxp-connections-fields;
            uses master-database-configuration;
        }
        output {
            leaf result {
                type boolean;
            }
        }
    }

    rpc delete-domain {
        description "Delete a domain from node";
        input {
            leaf node-id {
                type sxppt:node-id;
                mandatory true;
                description "SXP node ID";
            }
            leaf domain-name {
                type string;
                mandatory true;
            }
        }
        output {
            leaf result {
                type boolean;
            }
        }
    }

    rpc add-bindings {
        description "Add bindings to node";
        input {
            leaf domain-name {
                type string;
                default "global";
            }
            leaf node-id {
                type sxppt:node-id;
                mandatory true;
                description "SXP node ID";
            }
            uses master-database-configuration;
        }
        output {
            leaf result {
                type boolean;
            }
        }
    }

    rpc delete-bindings {
        description "Delete bindings from node";
        input {
            leaf node-id {
                type sxppt:node-id;
                mandatory true;
                description "SXP node ID";
            }
            leaf domain-name {
                type string;
                default "global";
            }
            uses master-database-configuration-fields;
        }
        output {
            leaf result {
                type boolean;
            }
        }
    }

    rpc add-domain-filter {
        description "Add new filter to Domain";
        input {
            leaf config-persistence {
                type config-persistence;
                default "pernament";
            }
            leaf requested-node {
                type sxppt:node-id;
                mandatory true;
                description "Node ID of the dedicated SXP source";
            }
            leaf domain-name {
                type string;
                default "global";
            }
            uses sxpfl:sxp-domain-filter;
        }
        output {
            leaf result {
                type boolean;
            }
        }
    }

    rpc delete-domain-filter {
        description "Removes filter from domain";
        input {
            leaf requested-node {
                type sxppt:node-id;
                mandatory true;
                description "Node ID of the dedicated SXP source";
            }
            leaf domain-name {
                type string;
                default "global";
            }
            leaf filter-specific {
                type sxpfl:filter-specific;
            }
            leaf filter-name {
                type string;
                default "base-domain-filter";
            }
        }
        output {
            leaf result {
                type boolean;
            }
        }
    }

    rpc add-connection-template {
        description "Delete a domain from node";
        input {
            leaf config-persistence {
                type config-persistence;
                default "pernament";
            }
            leaf node-id {
                type sxppt:node-id;
                mandatory true;
                description "SXP node ID";
            }
            leaf domain-name {
                type string;
                default "global";
            }
            uses sxpnd:sxp-connection-template-fields;
        }
        output {
            leaf result {
                type boolean;
            }
        }
    }

    rpc delete-connection-template {
        description "Delete a domain from node";
        input {
            leaf node-id {
                type sxppt:node-id;
                mandatory true;
                description "SXP node ID";
            }
            leaf domain-name {
                type string;
                default "global";
            }
            leaf template-prefix {
                type inet:ip-prefix;
                mandatory true;
                description "Ip prefix of the remote peers";
            }
        }
        output {
            leaf result {
                type boolean;
            }
        }
    }
}
