module sxp-controller-conf {
    yang-version 1;

    namespace "urn:opendaylight:params:xml:ns:yang:controller:sxp:controller:conf";
    prefix "sxpctrl-conf";

    import config {prefix config; revision-date 2013-04-05;}
    import opendaylight-md-sal-binding {prefix mdsal; revision-date 2013-10-28;}
    import sxp-database { prefix sxpdb; revision-date "2016-03-08";}
    import sxp-node { prefix sxpnd; revision-date "2016-03-08";}
    import sxp-protocol { prefix sxppt; revision-date "2014-10-02"; }

    organization "Cisco Systems, Inc.";

    contact "Martin Mihalek <mamihale@cisco.com>";

    description
        "Module defines the base YANG definitions for ODL-SXP-aware network node configuration.";

	revision "2014-10-02" {
        description
            "Reviewed revision of SXP controller configuration model";
    }

    // This is the definition of a service implementation
    identity sxp-controller {
        base config:module-type;
        config:java-name-prefix SxpController;
    }

	// ********************
    // Global Configuration
    // ********************

    augment "/config:modules/config:module/config:configuration" {
        case sxp-controller {
            when "/config:modules/config:module/config:type = 'sxp-controller'";

            container data-broker {
                uses config:service-ref {
                    refine type {
                        mandatory false;
                        config:required-identity mdsal:binding-async-data-broker;
                    }
                }
            }

            container sxp-controller {
                list sxp-node {
                    key "node-id";
                    leaf node-id {
                        type sxppt:node-id;
                        mandatory true;
                        description "SXP node ID";
                    }
                    uses sxpnd:sxp-node-identity-fields;
                    uses sxpnd:sxp-connections-fields;
                    uses sxpdb:master-database-configuration;
                }
            }
        }
    }
}
