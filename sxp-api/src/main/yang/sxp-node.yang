module sxp-node {
    yang-version 1;

    namespace "urn:opendaylight:sxp:node";
    prefix "sxpnd";

    import ietf-inet-types { prefix inet; revision-date "2013-07-15"; }
    import ietf-yang-types { prefix ietf-yang; revision-date "2013-07-15"; }
    import network-topology { prefix nt; revision-date "2013-10-21"; }
    import sxp-database { prefix sxpdb; revision-date "2016-03-08"; }
    import sxp-protocol { prefix sxppt; revision-date "2014-10-02"; }
    import sxp-filter { prefix sxpfl; revision-date "2015-09-11"; }
    import yang-ext { prefix ext; revision-date "2013-07-09"; }

    organization "Cisco Systems, Inc.";

    contact "Martin Mihalek <mamihale@cisco.com>";

    description
        "Module defines the base YANG definitions for SXP-aware network
        node.";

    revision "2016-03-08" {
        description
                "Reviewed revision of SXP node model";
    }

    // ***********************
    // Common Types Definition
    // ***********************

    typedef timer-type {
        type enumeration {
            enum delete-hold-down-timer;
            enum hold-timer;
            enum keep-alive-timer;
            enum reconciliation-timer;
            enum retry-open-timer;
        }
        description "Timer types with their default values";
    }

    typedef path-type {
        type enumeration {
            enum "PATH";
            enum "CLASSPATH";
        }
        description "SSL Certificate path type";
    }

    typedef store-type {
        type enumeration {
            enum "JKS";
            enum "PKCS12";
        }
        description "Certificates store type";
    }

    typedef security-type {
        type enumeration {
            enum "Default";
            enum "TLS";
        }
        description "Security protocol used for SXP peers";
    }

    // ****************
    // Common Groupings
    // ****************

    grouping tls-security-fields {
        container keystore {
            presence true;
            leaf location {
                description "keystore location";
                type string;
                mandatory true;
            }
            leaf type {
                description "keystore type (JKS or PKCS12)";
                type store-type;
                mandatory true;
            }
            leaf path-type {
                description "keystore path type (CLASSPATH or PATH)";
                type path-type;
                mandatory true;
            }
            leaf password {
                description "password protecting keystore";
                type string;
                mandatory true;
            }
        }
        container truststore {
            presence true;
            leaf location {
                description "truststore location";
                type string;
                mandatory true;
            }
            leaf type {
                description "truststore type (JKS or PKCS12)";
                type store-type;
                mandatory true;
            }
            leaf path-type {
                description "truststore path type (CLASSPATH or PATH)";
                type path-type;
                mandatory true;
            }
            leaf password {
                description "password protecting truststore";
                type string;
                mandatory true;
            }
        }
        leaf certificate-password {
            description "password protecting certificate";
            type string;
            mandatory true;
        }
    }

    grouping security-fields {
        leaf password {
            type string;
            description "SXP password for TCP-MD5 hashing can be up to 80 ASCII characters";
        }
        leaf md5-digest {
            type string;
            config false;
            description "16 bytes MD5 digest formed using the password as the key";
        }
        container tls {
            presence true;
            uses tls-security-fields;
            description "SSL keystores definitions";
        }
    }

    grouping capabilities-fields {
        container capabilities {
            config false;
            leaf-list capability {
                type sxppt:capability-type;
                description "Supported connection capabilities";
            }
        }
    }

    // ******************
    // SXP Node Groupings
    // ******************    

    grouping sxp-node-fields {
        leaf name {
            type string;
            description "SXP node name";
        }
        leaf enabled {
            type boolean;
            default "true";
            description "SXP protocol enabled/disabled";
        }
        leaf source-ip {
            type inet:ip-address;
            default "0.0.0.0";
            description "Default source IP address";
        }
        leaf tcp-port {
            type inet:port-number;
            default "64999";
            description "Server port";
        }
        leaf version {
            type sxppt:version;
            default "version4";
            description "Default global supported protocol version";
        }
        leaf mapping-expanded {
            type int32 {
                range "0..65635";
            }
            description "Network mappings to be expanded <0-65635>";
        }
        leaf description {
            type string;
        }
        container security {
            uses security-fields;
        }
    }

    grouping sxp-node-buffering-fields {
        leaf out-buffer {
            type int32 {
                range "1..150";
            }
            default 150;
            description "Buffer size for outgoing update messages";
        }
        leaf in-buffer {
            type int32;
            default 1000;
            description "Buffer size for incomming update messages";
        }
    }

    grouping sxp-databases-fields {
        container sxp-database {
            config false;
            uses sxpdb:sxp-database-fields;
            description "SXP database";
        }

        container master-database {
            uses sxpdb:master-database-fields;
            config false;
            description "IP-SGT-Master database";
        }
    }

    grouping sxp-connection-peer-fields {
        leaf node-id {
            type sxppt:node-id;
            config false;
            description "SXP node ID";
        }
        leaf state {
            type sxppt:connection-state;
            default "off";
            config false;
            description "Current state of the connection";
        }
        leaf timestamp-update-or-keep-alive-message {
            type ietf-yang:date-and-time;
            config false;
        }
    }

    grouping sxp-connection-template-fields {
        leaf template-prefix {
            type inet:ip-prefix;
            mandatory true;
            description "Ip prefix of the remote peers";
        }
        leaf template-password {
            type string;
            description "SXP password can be up to 80 ASCII characters";
        }
        leaf template-security-type {
            type security-type;
            default "Default";
            description "Security used for current SXP peer";
        }
        leaf template-tcp-port {
            type inet:port-number;
            default "64999";
            description "Port of the connected peers";
        }
        leaf template-mode {
            type sxppt:connection-mode;
            description "Mode of the connection, i.e. uni-directional or bi-directional
                        communication";
        }
        leaf template-version {
            type sxppt:version;
            default "version4";
            description "Negotiated and running SXP version between peers";
        }
        description "SXP connections to dedicated peers";
    }

    grouping sxp-connection-fields {
        leaf peer-address {
            type inet:ip-address;
            mandatory true;
            description "Address of the connected peer";
        }
        leaf tcp-port {
            type inet:port-number;
            mandatory true;
            description "Port of the connected peer";
        }
        leaf password {
            type string;
            description "SXP password can be up to 80 ASCII characters";
        }
        leaf security-type {
            type security-type;
            default "Default";
            description "Security used for current SXP peer";
        }
        leaf mode {
            type sxppt:connection-mode;
            mandatory true;
            description "Mode of the connection, i.e. uni-directional or bi-directional
                        communication";
        }
        leaf version {
            type sxppt:version;
            mandatory true;
            description "Negotiated and running SXP version between peers";
        }
        leaf description {
            type string;
            description "Description of the connection";
        }
        container connection-timers {
            uses sxp-listener-time-settings-fields;
            uses sxp-speaker-time-settings-fields;
        }
    }

    grouping sxp-connections-fields {
        container connections {
            list connection {
                key "peer-address tcp-port";
                uses sxp-connection-fields;
                uses sxp-connection-peer-fields;
                uses capabilities-fields;
                description "SXP connections to dedicated peers";
            }
        }
    }

    grouping sxp-connection-templates-fields {
        container connection-templates {
            list connection-template {
                key "template-prefix";
                uses sxp-connection-template-fields;
            }
        }
    }

    grouping sxp-node-time-settings-fields {
        leaf retry-open-time {
            type uint16;
            default 120;
            description "Retry Open Timer: Default timer value is 120 sec. If zero, timer
                        won't be used.";
        }
    }

    grouping sxp-listener-time-settings-fields {
        leaf delete-hold-down-time {
            type uint16;
            default 120;
            description "Delete Hold-down Timer: Default timer value is 120 sec. and it's
                        not configurable.";
        }
        leaf reconciliation-time {
            type uint16;
            default 120;
            description "Reconciliation Timer: Default timer value is 120 sec. If zero,
                        timer won't be used.";
        }
        leaf hold-time {
            type uint16;
            default 90;
            description "Optional Hold Timer: Default timer value is 90 sec. and can be
                        configurable. The actual value used for a connection is negotiated.";
        }
        leaf hold-time-min {
            type uint16;
            default 90;
        }
        leaf hold-time-max {
            type uint16;
            default 180;
        }
    }

    grouping sxp-speaker-time-settings-fields {
        leaf hold-time-min-acceptable {
            type uint16;
            default 120;
        }
        leaf keep-alive-time {
            type uint16;
            default 30;
            description "Optional Keep-alive Timer: Default timer value is 30 sec. and
                        can be configurable. The actual value used for a connection is
                        set to 1/3 of negotiated Hold Time and can be further restarted
                        with a random jitter.";
        }
    }

    grouping sxp-domain-fields {
        leaf domain-name {
            type string;
        }
        uses sxp-databases-fields;
        uses sxp-connections-fields;
        uses sxp-connection-templates-fields;
        container domain-filters {
            list domain-filter {
                key "filter-specific filter-name";
                uses sxpfl:sxp-domain-filter-fields;
            }
        }
    }

    // ********************
    // Global Configuration
    // ********************

    grouping sxp-node-identity-fields {
        uses sxp-node-fields;
        uses capabilities-fields;
        container timers {
            uses sxp-node-time-settings-fields;
            uses sxp-listener-time-settings-fields;
            uses sxp-speaker-time-settings-fields;
        }
    }

    augment /nt:network-topology/nt:topology/nt:node {
        ext:augment-identifier "sxp-node-identity";
        uses sxp-node-identity-fields;
        container sxp-domains {
            presence "SXP domains containing bindings";
            list sxp-domain {
                key "domain-name";
                uses sxp-domain-fields;
                min-elements 1;
            }
        }
        container sxp-peer-groups {
            uses sxpfl:sxp-peer-groups;
        }
        container message-buffering {
            uses sxp-node-buffering-fields;
        }
    }
}
