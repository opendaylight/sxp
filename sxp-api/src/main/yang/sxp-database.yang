module sxp-database {
    yang-version 1;

    namespace "urn:opendaylight:sxp:database";
    prefix "sxpdb";

    import ietf-inet-types { prefix inet; revision-date "2013-07-15"; }
    import ietf-yang-types { prefix ietf-yang; revision-date "2013-07-15"; }
    import sxp-protocol { prefix sxppt; revision-date "2014-10-02"; }
    import sxp-config { prefix sxpcfg; revision-date "2018-06-11"; }

    organization "Cisco Systems, Inc.";

    contact "Martin Mihalek <mamihale@cisco.com>";

    description
        "Module defines the base YANG definitions for SXP databases.";

    revision "2016-03-08" {
        description
                "Reviewed revision of SXP database model";
    }

    // ***********************
    // Common Types Definition
    // ***********************

    typedef sgt {
        type uint16;
        description "Source group tag";
    }

    // ***********************
    // SXP Databases Groupings
    // ***********************

    grouping sxp-binding-fields {
        leaf ip-prefix {
            type inet:ip-prefix;
            mandatory true;
        }
        leaf security-group-tag {
            type sgt;
            mandatory true;
        }
        leaf timestamp {
            type ietf-yang:date-and-time;
            description "Time when a node received a binding to trace most recently received
                                    bindings";
        }
        leaf origin {
            mandatory true;
            type leafref {
                path "/sxpcfg:binding-origins/sxpcfg:binding-origin/sxpcfg:origin";
            }
        }
        uses peer-sequence-fields;
    }

    grouping peer-sequence-fields {
        container peer-sequence {
            description "Peer sequence of node IDs (IPv4|IPv6 support) that represents
                        a path through which the binding has been traversing";
            list peer {
                key "seq";
                leaf seq {
                    type uint16;
                }
                leaf node-id {
                    type sxppt:node-id;
                }
            }
        }
    }

    grouping sxp-database-fields {
        list binding-database {
            key "binding-type";
            leaf binding-type {
                type enumeration {
                    enum active-bindings;
                    enum tentative-bindings;
                }
            }
            container binding-sources {
                list binding-source {
                    key "source-id";
                    leaf source-id {
                        type sxppt:node-id;
                    }
                    container sxp-database-bindings {
                        list sxp-database-binding {
                            key "ip-prefix security-group-tag";
                            uses sxp-binding-fields;
                        }
                    }
                }
            }
        }
    }

    grouping master-database-fields {
        description "The master database preserves sxp-database structure to simplify
                copying the items between databases and UPDATE message construction
                process.";
        list master-database-binding {
            key "ip-prefix";
            uses sxp-binding-fields;
        }
    }
}
