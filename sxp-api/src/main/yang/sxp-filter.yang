module sxp-filter {
    yang-version 1;

    namespace "urn:opendaylight:sxp:filter";
    prefix "sxpfl";

    import ietf-inet-types {prefix inet; revision-date "2013-07-15";}
    import sxp-database {prefix sxpdb; revision-date "2016-03-08";}

    organization "Cisco Systems, Inc.";

    contact "Martin Mihalek <mamihale@cisco.com>";

    description "Module defines the base YANG definitions for SXP filtering.";

    revision "2015-09-11" {
        description "Reviewed revision of SXP filtering model";
    }

    // ***********************
    // Common Types Definition
    // ***********************

    typedef filter-type {
        type enumeration {
            enum inbound;
            enum inbound-discarding;
            enum outbound;
        }
        description "Type specifying direction of sgt/prefix filtering, while using inbound-discarding
                 SXP-DB may get to inconsistent state after Filter update so reconnecting peer is needed or use
                  of inbound filter that handles this situation.";

    }

    typedef filter-specific {
        type enumeration {
            enum access-or-prefix-list;
            enum peer-sequence;
        }
        description "Type specifying logic used to filter bindings.";
    }

    typedef filter-update-policy {
        type enumeration {
            enum auto-update;
            enum manual-update;
        }
        description "Type specifying if changes in filter are propagated to peers automaticly.";
    }

    typedef filter-entry-type {
        type enumeration {
            enum permit;
            enum deny;
        }
        description "Filter entry flag";
    }

    typedef mask-range-operator {
        type enumeration {
            enum ge;
            enum le;
            enum eq;
        }
        description "Operators for specifying mask range in prefix list";
    }

    typedef wildcard-mask {
        type inet:ip-address;
        description "Address mask";
    }

    typedef prefix-list-mask {
        type uint8 {
            range "0..128";
        }
        description "Address mask";
    }

    // ******************
    // SXP Filter Groupings
    // ******************

    grouping sxp-peer-groups {
        list sxp-peer-group {
            key "name";
            uses sxp-peer-group-fields;
        }
    }

    grouping sxp-peer-group {
        container sxp-peer-group {
            uses sxp-peer-group-fields;
        }
    }

    grouping sxp-peer-group-fields {
        leaf name {
            type string;
            mandatory true;
            description "Name of peer group";
        }
        container sxp-peers {
            list sxp-peer {
                key "peer-address";
                uses sxp-peer-fields;
            }
        }
        list sxp-filter {
            key "filter-type filter-specific";
            uses sxp-filter-fields;
        }
    }

    grouping sxp-filter {
        container sxp-filter {
            uses sxp-filter-fields;
        }
    }


    grouping sxp-domain-filter {
        container sxp-domain-filter {
            uses sxp-domain-filter-fields;
        }
    }

    grouping sxp-peer-fields {
        leaf peer-address {
            type inet:ip-address;
            mandatory true;
            description "Address of the connected peer";
        }
        leaf peer-port {
            type inet:port-number;
            default "64999";
            description "Port of the connected peer";
        }
    }

    grouping sxp-filter-fields {
        leaf filter-type {
            type filter-type;
            mandatory true;
            description "Inbound/Outbound";
        }
        leaf filter-specific {
            type filter-specific;
        }
        leaf filter-policy {
            type filter-update-policy;
            default manual-update;
        }
        uses filter-entries-fields;
    }

    grouping sxp-domain-filter-fields {
        leaf filter-specific {
            type sxpfl:filter-specific;
        }
        leaf filter-name {
            type string;
            default "base-domain-filter";
        }
        container domains {
            list domain {
                key "name";
                leaf name {
                    type string;
                }
            }
        }
        uses sxpfl:filter-entries-fields;
    }

    grouping filter-entries-fields {
        choice filter-entries {
            mandatory "true";
            description "Filter entries specifying filter.";
            case acl-filter-entries {
                list acl-entry {
                    key "entry-seq";
                    uses acl-entry;
                    min-elements 1;
                }
            }
            case prefix-list-filter-entries {
                list prefix-list-entry {
                    key "entry-seq";
                    uses prefix-list-entry;
                    min-elements 1;
                }
            }
            case peer-sequence-filter-entries {
                list peer-sequence-entry {
                    key "entry-seq";
                    uses peer-sequence-entry;
                    min-elements 1;
                }
            }
        }
    }

    grouping sgt-match-fields {
        choice sgt-match {
            case sgt-matches {
                leaf-list matches {
                    type sxpdb:sgt;
                    min-elements 1;
                    description "SGT values";
                }
            }
            case sgt-range {
                leaf sgt-start {
                    type sxpdb:sgt;
                    mandatory true;
                    description "Start value of SGT range";
                }
                leaf sgt-end {
                    type sxpdb:sgt;
                    mandatory true;
                    description "End value of SGT range";
                }
            }
        }
    }

    grouping acl-match-fields {
        leaf ip-address {
            type inet:ip-address;
            mandatory true;
            description "Address on which mask will be applied";
        }
        leaf wildcard-mask {
            type wildcard-mask;
            mandatory true;
            description "Wildcard mask applied to address";
        }
        container mask {
            presence "Extended ACL is used for filtering";
            leaf address-mask {
                type inet:ip-address;
                mandatory true;
                description "Address Mask";
            }
            leaf wildcard-mask {
                type wildcard-mask;
                mandatory true;
                description "Wildcard mask for mask";
            }
        }
    }

    grouping prefix-list-match-fields {
        leaf ip-prefix {
            type inet:ip-prefix;
            mandatory true;
            description "Prefix specifying filter";
        }
        container mask {
            presence "Extended PL is used for filtering";
            leaf mask-range {
                type mask-range-operator;
                mandatory true;
                description "Range used on mask";
            }
            leaf mask-value {
                type prefix-list-mask;
                mandatory true;
                description "Mask used for comparison";
            }
        }
    }

    grouping acl-entry {
        leaf entry-type {
            type filter-entry-type;
            mandatory true;
            description "PERMIT/DENY";
        }
        leaf entry-seq {
            type uint16;
            mandatory true;
            description "Specifying order of each entry.";
        }
        container acl-match {
            presence "ACL match will be used for filtering";
            uses acl-match-fields;
        }
        uses sgt-match-fields;
    }

    grouping prefix-list-entry {
        leaf entry-type {
            type filter-entry-type;
            mandatory true;
            description "PERMIT/DENY";
        }
        leaf entry-seq {
            type uint16;
            mandatory true;
            description "Specifying order of each entry.";
        }
        container prefix-list-match {
            presence "PL match will be used for filtering";
            uses prefix-list-match-fields;
        }
        uses sgt-match-fields;
    }

    grouping peer-sequence-entry {
        leaf entry-type {
            type filter-entry-type;
            mandatory true;
            description "PERMIT/DENY";
        }
        leaf entry-seq {
            type uint16;
            mandatory true;
            description "Specifying order of each entry.";
        }
        leaf peer-sequence-length {
            type uint16;
            mandatory true;
            description "Length of sequence";
        }
        leaf peer-sequence-range {
            type mask-range-operator;
            mandatory true;
            description "Range used on sequence";
        }
    }
}
